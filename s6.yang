module network-failover {
  namespace "urn:network:failover";
  prefix nf;

  container topology {
    list node {
      key "id";
      leaf id {
        type string;
      }
      leaf active {
        type boolean;
      }
    }
  }

  container failover-decision {
    leaf target-node {
      type string;
    }
    leaf failover-executed {
      type boolean;
    }
  }
}
