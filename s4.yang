module service-autoscaling {
  namespace "urn:service:autoscaling";
  prefix sas;

  container scaling-state {
    leaf active-users {
      type uint32;
    }
    leaf performance-degraded {
      type boolean;
    }
    leaf compute-instances {
      type uint16;
    }
    leaf scaling-action {
      type enumeration {
        enum scale-up;
        enum scale-down;
        enum no-change;
      }
    }
  }
}
