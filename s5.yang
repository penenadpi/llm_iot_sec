module config-update-control {
  namespace "urn:config:update-control";
  prefix cuc;

  container update-state {
    leaf config-change-needed {
      type boolean;
    }
    leaf restart-triggered {
      type boolean;
    }
    leaf service-available {
      type boolean;
    }
  }
}
