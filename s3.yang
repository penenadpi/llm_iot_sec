module gateway-alert-consistency {
  namespace "urn:gateway:alert-consistency";
  prefix gac;

  container detection-state {
    leaf wifi-failure {
      type boolean;
    }
    leaf lorawan-failure {
      type boolean;
    }
    leaf alert-issued {
      type boolean;
    }
  }
}
