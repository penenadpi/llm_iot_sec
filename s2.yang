module gateway-interface-monitor {
  namespace "urn:gateway:interface-monitor";
  prefix gim;

  container interfaces {
    list interface {
      key "name";
      leaf name {
        type string;
      }
      leaf enabled {
        type boolean;
      }
      leaf failure-detected {
        type boolean;
      }
    }
  }

  leaf alert-issued {
    type boolean;
  }
}
