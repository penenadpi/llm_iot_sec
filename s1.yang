module gateway-failure-policy {
  namespace "urn:gateway:failure-policy";
  prefix gfp;

  container failure-handling {
    leaf device-failure-detected {
      type boolean;
    }
    leaf alert-issued {
      type boolean;
    }
    leaf forwarding-enabled {
      type boolean;
    }
  }
}
